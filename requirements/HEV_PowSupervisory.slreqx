# HEV_PowSupervisory
HEV_PowSupervisory Algorithm Requirement Specification

Spec Version : 1.0

## #1: Algorithm For HEV System Power Management (Container)
The following requirement describes the design and implementation details for System Power Management of HEV.

## #2: System Framework (Informational)
The framework consists of ON/OFF states of the engine, motor, and generator and respective transition between different states based on various conditions

## #4: Operation Modes (Container)
The algorithm should comprise of 4 modes
- Low Speeds/Start
- Acceleration
- Cruising
- Braking
The following switching mechanism is applied between the states :-
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
### #5: Low speeds/Start (Functional)
The electric motor provides all the torque for initial acceleration

### #6: Acceleration (Functional)
As the vehicle reaches a predefined speed, the engine kicks in to supply power along with the motor.

### #7: Cruising (Functional)
If the car maintains constant speed, the motor is switched off and the generator is switched on. A portion of the engine’s power is used by the generator to recharge the battery.

### #9: Braking (Functional)
If brakes are applied, the engine and the generator are switched off. The motor is made to behave like a generator to recharge the battery.

## #10: Inputs (Container)
Specification of Inputs used by the Algorithm

### #12: Speed (Functional)
This signal is the vehicle speed, expressed in km/h.

### #13: Brake (Functional)
This input specifies the Brake signal.

### #14: Charge (Functional)
This input signal the battery Charge percentage value. Range is 0-100%.

### #15: Engine Speed (Functional)
This signal specifies the engine speed used by the algorithm

## #11: Outputs (Container)
Specification of Algorithm Outputs

### #16: Motor Enable (Functional)
Electric Motor Enable Signal

### #17: Generator Enable (Functional)
Status Generator for charging information

### #18: Engine Enable (Functional)
Status of ICE Engine - Enabled or Disabled

## #19: Constant (Functional)
Specification of Constants used by the Algorithm

### #20: Engine On Speed (Informational)
Engine ON Speed or EngOnRPM specifies the Engine RPM beyond which the ICE get enabled

### #21: Engine Off RPM (Informational)
Engine OFF Speed or EngOffRPM specifies the Engine RPM below which the ICE gets disabled
